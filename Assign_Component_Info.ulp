/*
    Manufacturer & Part Number attribute assigner ULP for EAGLE.
    Written by Sami Koistinen in 2016.

    How to use:
    1. Run the script.
    2. Write Manufacturer (MF) and Manufacturer Part Number (MPN) into the two text boxes.
    3. Select a component from the list.
    4. After clicking "ASSIGN ATTRIBUTES" button, all components with the selected component's Value/Device/Package combination will be assigned the MF and MPN attributes you just defined.

    Use this ULP with your own risk.
    I take no responsibility whatsoever of anything that might happen to anyone/anything using this script.
*/

#usage  "Assign_Component_Info"


//
// Build component list
//

string Parse_Description(string source_text)
{
    char   previous_character[] = { 0, 0 };
    string result_text;
    int    is_inside_tag = 0;
    int    parsing_ready = 0;
    int    text_length   = strlen(source_text);

    for (int i = 0; i < text_length && !parsing_ready; i++)
    {
        if (source_text[i] == '<')
            is_inside_tag = 1;

        if (!is_inside_tag)
            result_text += source_text[i];

        if (source_text[i] == '>')
        {
            if ((previous_character[1] == 'b' || previous_character[1] == 'B') &&
                (previous_character[0] == 'r' || previous_character[0] == 'R'))
                parsing_ready = 1;

            is_inside_tag = 0;
        }

        previous_character[1] = previous_character[0];
        previous_character[0] = source_text[i];
    }

    return result_text;
}


string part_name[];
string part_value[];
string part_device_name[];
string part_device_package[];
int    part_sheet[];

string part_info[];
int    part_count = 0;

schematic(current_schematic)
{
    current_schematic.parts(part)
    {
        // Basic info
        part_name[part_count]           = part.name;
        part_value[part_count]          = part.value;
        part_device_name[part_count]    = part.device.name;
        part_device_package[part_count] = part.device.package.name;

        part.instances(instance)
        {
            part_sheet[part_count] = instance.sheet;
        }       

        part_info[part_count]  = part.name;
        part_info[part_count] += "\t" + Parse_Description(part.device.description);
        part_info[part_count] += "\t" + part.value;
        part_info[part_count] += "\t" + part.device.name;
        part_info[part_count] += "\t" + part.device.package.name;

        // Count the number of pads and drills
        int pad_count   = 0;
        int drill_count = 0;
        part.device.package.contacts(contact)
        {
            pad_count++;

            if (contact.pad)
                if (contact.pad.drill != 0)
                    drill_count++;
        }

        // Number of pads
        string pad_count_string;
        sprintf(pad_count_string, "\t%d", pad_count);
        part_info[part_count] += pad_count_string;

        // Through hole technology?
        if (!drill_count)
        {
            part_info[part_count] += "\tNo";
        } else {
            if (drill_count == pad_count)
                part_info[part_count] += "\tYes";
            else
                part_info[part_count] += "\tERROR!!!";
        }

        // Manufacturer & Part Order Number
        string manufacturer = " ";
        string part_id      = " ";
        string shop         = " ";
        string info         = " ";

        if (part.attribute["MF"])
            manufacturer = part.attribute["MF"];

        if (part.attribute["MPN"])
            part_id = part.attribute["MPN"];

        if (part.attribute["SHOP"])
            shop = part.attribute["SHOP"];

        if (part.attribute["INFO"])
            info = part.attribute["INFO"];

        part_info[part_count] += "\t" + manufacturer;
        part_info[part_count] += "\t" + part_id;
        part_info[part_count] += "\t" + shop;

        part_info[part_count] = strupr(part_info[part_count]);

        part_info[part_count] += "\t" + info;

        part_count++;
    }
}



//
// Display BOM
//

string manufacturer_name;
string manufacturer_part_id;
string shop_name;
string info_note;
int    selected_part = 0;


int result = dlgDialog("Manufacturer & Part Number Assigner")
{
    dlgHBoxLayout
    {
        dlgLabel("Manufacturer (MF):");
        dlgStringEdit(manufacturer_name);

        dlgLabel("Manufacturer Part Number (MPN):");
        dlgStringEdit(manufacturer_part_id);

        dlgLabel("Where To Buy (SHOP):");
        dlgStringEdit(shop_name);

        dlgLabel("Source/Link/Datasheet/Note:");
        dlgStringEdit(info_note);
    };

    dlgLabel("Select Value/Device/Package reference component from the below list.");
    dlgLabel("Manufacturer/Part Number/Shop/Note attributes will be added to ALL similar components.");
    dlgListView("Part ID/Reference\tDescription\tValue\tDevice\tPackage\tPads\tTHT\tMF\tMPN\tShop\tSource/Link/Datasheet/Note", part_info, selected_part);

    dlgPushButton("+&ASSIGN ATTRIBUTES") dlgAccept();
    dlgPushButton("-Cancel") dlgReject();
};



//
// Assign MF & MPN attributes
//

string result_string;

if (result)
{
    result_string += "CHANGE DISPLAY OFF;\n";

    for (int i = 0; i < part_count; i++)
    {
        if (part_value[i] == part_value[selected_part] &&
            part_device_name[i] == part_device_name[selected_part] &&
            part_device_package[i] == part_device_package[selected_part])
        {
            string temp_sheet;
            string temp_string1;
            string temp_string2;
            string temp_string3;
            string temp_string4;

            sprintf(temp_sheet, "EDIT .S%d;\n", part_sheet[i]);
            sprintf(temp_string1, "ATTRIBUTE %s %s '%s';\n", part_name[i], "MF", manufacturer_name);
            sprintf(temp_string2, "ATTRIBUTE %s %s '%s';\n", part_name[i], "MPN", manufacturer_part_id);
            sprintf(temp_string3, "ATTRIBUTE %s %s '%s';\n", part_name[i], "SHOP", shop_name);
            sprintf(temp_string4, "ATTRIBUTE %s %s '%s';\n", part_name[i], "INFO", info_note);

            result_string += temp_sheet;
            result_string += temp_string1;
            result_string += temp_string2;
            result_string += temp_string3;
            result_string += temp_string4;
        }
    }
}


exit(result_string);
